# Requirements_Client

## Client_01: Type Vehicle (Functional)
The develop vehicle must have 4 wheels

## Client_02: Electric_car (Functional)
Vehicle must be electric and use a bateries cell

## Client_03: Spped vehicle (Functional)
The vehicle shall reach a speed of 30 km/h

## Client_04: Dimension (Functional)
The vehicle must have standard measurements of a radio-controlled car, comfortable to transport

## Client_05: Vision_first_person (Functional)
The vehicle shall incomporate a camera to transmit video to station control

## Client_06: Control_vehicle (Functional)
The vehicle must be driven using a steering wheel connected to a PC
